module ins-interfaces {
    yang-version 1.1;

    namespace
        "https://ost.ch/ins/yang/ins-interfaces";

    prefix if;

    organization
        "INS Institute for Networked Solutions";

    contact
        "Support: <https://ost.ch/ins/>";

    description
        "Learn YANG by creating some models here.";

    revision "2021-09-14" {
        description
            "Initial Revision";
            reference
                "YANG@INS";
    }

    typedef ipv4-address {
        type string {
            pattern
            '(([0-9]|[1-9][0-9]|1[0-9][0-9]|2[0-4][0-9]|25[0-5])\.){3}'
        +  '([0-9]|[1-9][0-9]|1[0-9][0-9]|2[0-4][0-9]|25[0-5])'
        + '(%[\p{N}\p{L}]+)?';
        }
    description
      "The ipv4-address type represents an IPv4 address in
       dotted-quad notation.  The IPv4 address may include a zone
       index, separated by a % sign.
       The zone index is used to disambiguate identical address
       values.  For link-local addresses, the zone index will
       typically be the interface index number or the name of an
       interface.  If the zone index is not present, the default
       zone of the device will be used.
       The canonical format for the zone index is the numerical
       format";
  }

    container interfaces {
        list interface {
            leaf name {
                type string;
                mandatory "true";
                description
                    "Interface name.";
            }
            leaf address {
                type ipv4-address;
                mandatory "true";
                description
                    "Interface IP address.";
            }
            leaf mac {
                type ipv4-address;
                mandatory "true";
                description
                    "Interface MAC address.";
            }
            leaf status {
                type boolean;
                description
                    "Interface status.";
            }
            key "name";
        }
    }
}
